# UI and CLI

## #1: CLI: Run backtesting with configuration (Functional)

## #2: CLI: Select and run agents (Functional)

## #3: CLI: Show backtesting results (Functional)

## #4: CLI: Show market information (Functional)
