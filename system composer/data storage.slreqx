# data storage

## #1: Store historical data (Container)
Each parquet file corresponds to one-day tick data of different exchanges and assets, and contains the information of price and time.

## #2: Store system loggings (Container)

## #3: Provide historical market data to other module via service (Functional)

## #4: Provide system loggings to UI/CLI (Functional)
