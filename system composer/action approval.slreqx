# action approval

## #1: Request backtesting results (Functional)

## #2: Request risk metrics (Functional)

## #3: Send order to gateway when approved (Functional)

## #4: Publish rejection of orders for logging (Functional)
