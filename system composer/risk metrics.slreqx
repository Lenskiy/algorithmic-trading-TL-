# risk metrics

## #1: Request historical data from data storage (Functional)

## #2: Calculate VaR, liquidity risks and capital risks in parallel (Functional)

## #3: Provide calculation functions to action approval (Functional)
