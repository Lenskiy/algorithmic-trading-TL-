# backtesting

## #1: Request historical data from data stroage (Functional)

## #2: Accepts market orders and limit orders from agents (Functional)

## #3: Communicate with Testing Action Approval (Functional)

## #4: Calculate performance of testing (Functional)

## #5: Have different backtesting scenarios (Functional)
