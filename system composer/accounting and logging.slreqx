# accounting and logging

## #1: Listen to order creation (Functional)

## #2: Listen to order rejection by Action Approval (Functional)

## #3: Listen to order confirmation from gateway (Functional)

## #4: Listen to backtesting events (Functional)

### #5: Listen to backesting initiation (Functional)

### #6: Listen to backtesting results (Functional)

## #7: Store events in data storage (Functional)
