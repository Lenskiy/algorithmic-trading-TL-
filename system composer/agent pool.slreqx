# agent pool

## #1: Calculate the initial state with supplement of backtesting data (Functional)

## #2: Agents know the current position of themselves (Functional)

## #3: Agents send trading signal to action approval (Functional)

## #4: Agents run in multiple threads (Functional)
