# gateway

## #1: Receive tick data from APIs (Functional)

## #2: Publish tick data via Topics (Functional)

## #3: Able to send different types of orders (Functional)
- Market orders
- Limit orders

## #4: Receive order confirmaton from APIs (Functional)

## #5: Publish order confirmations via Topics (Functional)
